FME workspace Create_and_update_pre-fill_files.fmw

Parameters:
- SourceDataset_TEXTLINE = Reports_to_use.txt   # Source Text File(s)
- output_filename = dummytext-leave-it   # dummytext for filenames

Readers:
- TEXTLINE_1: TEXTLINE from $(SourceDataset_TEXTLINE)

Note: Read file urls to process
text_line (reader TEXTLINE_1)
    attributes: text_line_data buffer
    -> AttributeSplitter
Note: Extract URL parts to build filename
AttributeSplitter
    LIST_NAME = _list
    TRIM_OPTION = Both
    DROP_EMPTY_PARTS = Yes
    DELIMITER = /
    ATTR_NAME = text_line_data
    -> AttributeCreator
Note: Create filename for output
AttributeCreator
    ATTR_LIST = $(output_filename),"FME_CONDITIONAL:DEFAULT_VALUE'@LowerCase(@Value(_list{2}))_mmr-pam_report.xml'BOOL_OP;OR;COMPOSITE_TEST;<Unused>;TEST @Value(_list{2}) = ec'@LowerCase(@Substring(@Value(_list{7}),0,2))_mmr-pam_report.xml'FME_NUM_CONDITIONS2___"
    -> HTTPCaller
Note: Fetch file from CDR
HTTPCaller
    CONNECTION_TIMEOUT_LENGTH = 60
    STATUS_CODE_ATTR = _http_status_code
    TRANSFER_TIMEOUT_LENGTH = 90
    TARGET_URL = @Value(text_line_data)
    ERROR_ATTR = _error
    HTTP_METHOD = GET
    RESPONSE_HEADER_LIST_ATTR = _headers
    TARGET_ATTR_ENCODING = auto-detect
    SAVE_FILE = Attribute
    TARGET_ATTR = _response_body
    FOLLOW_REDIRECTS = Yes
    VERIFY_SSL_CERTIFICATES = No
    USE_COOKIES = No
    -> XSLTProcessor
Note: Use XSLT to clear values and save on disk
XSLTProcessor
    ATTRIBUTE_XML = _response_body
    FILE_RESULTS = $(output_filename)
    EMBEDDED_STYLESHEET:
      <xsl:stylesheet version="2.0" xmlns:xsl="http://www.w3.org/1999/XSL/Transform">

          <xsl:output method="xml" indent="yes" omit-xml-declaration="no"/>
          <!--<xsl:strip-space elements="*"/>-->

          <xsl:template match="node()|@*">
              <xsl:copy>
                  <xsl:apply-templates select="node()|@*"/>
              </xsl:copy>
          </xsl:template>

          <xsl:template match="MMR_PAMs/MMR_PAM/Table1/UnionPolicy">
            <xsl:for-each select=".">
              <xsl:if test=". != 'Non_EU-related_PaM'">
                <xsl:copy-of select="."/>
              </xsl:if>
            </xsl:for-each>
          </xsl:template>

      </xsl:stylesheet>
    XML_INPUT_TYPE = Attribute with XML Document
    CONFIGURATION_TYPE = Embedded Stylesheet
    RESULTS_TYPE = Results Written to File
    TRANSFORMED -> HTTPCaller_2
Note: Push updated file to CDR folder / (update URL for prod/test and / also the user credentials)
HTTPCaller_2
    CONNECTION_TIMEOUT_LENGTH = 60
    UPLOAD_TYPE = Multipart / Form Data
    STATUS_CODE_ATTR = _http_status_code
    TRANSFER_TIMEOUT_LENGTH = 90
    TARGET_URL = http://cdr.eionet.europa.eu/xmlexports/mmr_pam/manage_addProduct/OFSP/manage_addFile
    ERROR_ATTR = _error
    HTTP_METHOD = POST
    RESPONSE_HEADER_LIST_ATTR = _headers
    TARGET_ATTR_ENCODING = auto-detect
    MULTIPARTS = id StringUpload SOURCE_EXPRESSION;@Value($(output_filename));MIME_TYPE;text/plain;FME_CONTROLLER_QUERY_FILE;transformers\dependencies\http\StringUpload.fme file FileUpload SOURCE_FILE;@Value($(output_filename));MIME_TYPE;application/xml;FME_CONTROLLER_QUERY_FILE;transformers\dependencies\http\FileUpload.fme
    SAVE_FILE = Attribute
    TARGET_ATTR = _response_body
    AUTH_METHOD = Basic
    FOLLOW_REDIRECTS = Yes
    AUTH_PASSWORD =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
    AUTH_USERNAME = [user]
    VERIFY_SSL_CERTIFICATES = Yes
    USE_COOKIES = No
